kofn-Composite-Crypto-2023
     { joint-iso-itu-t(2) country(16) us(840) organization(1) OpenCA(18277) 
       Algorithms(2) PublicKey(1) kofn-CompositeCrypto(2) }

DEFINITIONS IMPLICIT TAGS ::= BEGIN

EXPORTS ALL;

IMPORTS
  PUBLIC-KEY, SIGNATURE-ALGORITHM, AlgorithmIdentifier{}
    FROM AlgorithmInformation-2009  -- RFC 5912 [X509ASN1]
      { iso(1) identified-organization(3) dod(6) internet(1)
        security(5) mechanisms(5) pkix(7) id-mod(0)
        id-mod-algorithmInformation-02(58) }

  SubjectPublicKeyInfo
    FROM PKIX1Explicit-2009
      { iso(1) identified-organization(3) dod(6) internet(1)
        security(5) mechanisms(5) pkix(7) id-mod(0)
        id-mod-pkix1-explicit-02(51) }

  OneAsymmetricKey
    FROM AsymmetricKeyPackageModuleV1
      { iso(1) member-body(2) us(840) rsadsi(113549) pkcs(1)
        pkcs-9(9) smime(16) modules(0)
        id-mod-asymmetricKeyPkgV1(50) } 
       
;       
        
--
-- Object Identifiers
--

-- Defined in ITU-T X.690
der OBJECT IDENTIFIER ::=
  {joint-iso-itu-t asn1(1) ber-derived(2) distinguished-encoding(1)}

id-kofn-CompositeCrypto OBJECT IDENTIFIER ::= {
  iso(1) identified-organization(3) dod(6)
  internet(1) private(4) enterprise(1) OpenCA(18227)
  Algorithms(2) PublicKey(1) Experimental(999)
  kofn-CompositeCrypto(2)
}

id-ce-deprecatedKeyTypes OBJECT IDENTIFIER ::= { 
  iso(1) identified-organization(3) dod(6) 
  internet(1) private(4) enterprise(1) OpenCA(18227)
  Extensions(3) deprecated-algs (2) 
}

id-ce-requiredKeyTypes OBJECT IDENTIFIER ::= { 
  iso(1) identified-organization(3) dod(6) 
  internet(1) private(4) enterprise(1) OpenCA(18227)
  Extensions(3) required-algs (3)
}

--
-- Constants
--

MaxComponents INTEGER ::= 16
      -- Maximum number of allowed components in a Key

MaxThreshold INTEGER ::= 15
      -- Maximum value for required algoritmic threshold

CompositeThreshold ::= INTEGER (1..MaxThreshold)
      -- Allowed value ranges for the K-of-N threshold (K)

--
-- Private Keys
--

kofn-CompositePrivateKey ::= SEQUENCE SIZE (2..MaxComponents)
  OF OneAsymmetricKey

kofn-CompositeParams ::= SEQUECE {
  hashAlgorithm           AlgorithmIdentifier,
    -- Identifier for the hash algorithm used to pre-hash the message
  threshold               CompositeThreshold OPTIONAL,
    -- Number of required supported algorithms (must be less than N)
}

--
-- Public Keys
--

kofn-CompositePublicKeyParams ::= SEQUENCE {
  params                  kofn-CompositeParams,
  componentsParams        SEQUENCE SIZE (1..MaxComponents)
      OF AlgorithmIdentifier,
}

pk-kofn-CompositePublicKey PUBLIC-KEY ::= {
   id id-kofn-CompositeCrypto
   KeyValue pk-kofn-CompositePublicKey
   Params TYPE kofn-CompositePublicKeyParams ARE required
   PrivateKey kofn-CompositePrivateKey
}

--
-- Signature Algorithm
--

kofn-CompositeSignatureParams ::= SEQUENCE {
  componentsParams    SEQUENCE SIZE 
      (1..MaxComponents) OF AlgorithmIdentifier,
  hashAlgorithm   OBJECT IDENTIFIER OPTIONAL,
}

kofn-CompositeComponentSignatureValue ::= SEQUENCE 
    SIZE (1..MaxComponents) OF BIT STRING
 
sa-kofn-CompositeSignature SIGNATURE-ALGORITHM ::= {
      IDENTIFIER id-kofn-CompositeCrypto
      VALUE kofn-CompositeSignatureValue
      PARAMS TYPE kofn-CompositeSignatureParams ARE optional
      PUBLIC-KEYS { pk-kofn-CompositePublicKey }
      SMIME-CAPS { IDENTIFIED BY id-kofn-CompositeCrypto }
}

--
-- Extensions
--

DeprecatedKeyTypes ::= SEQUENCE SIZE (1..MaxThreshold) 
      OF OBJECT IDENTIFIER

RequiredKeyTypes ::= SEQUENCE SIZE (1..MaxThreshold) 
      OF OBJECT IDENTIFIER

END
